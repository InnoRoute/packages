module TNflowtable-actions {
    namespace "TrustNode:flow:actions";
    prefix flow;
    import ietf-inet-types {prefix inet; revision-date "2013-07-15";}
    import ietf-yang-types {prefix yang; revision-date "2010-09-24";}
		description 
		"TrustNode FlowCache action datamodel";
    revision "2019-02-01" {
        description "Initial revision";
    }

 grouping action {
        choice action {
            case output-action-case {
                container output-action {
                    leaf output-port {
                        type uint8;
                    }                    
                    }
            }
            case drop-action-case {
                container drop-action {
                    leaf drop-reason {
                        type uint16;
                    }                    
                    }
            }
            case modify-action-case {
            container modify-action {
            		choice modfield{
            			case MAC-DST{
            				leaf MAC-DST-overwrite{
            					type yang:mac-address;
            				}
            			}
            			case MAC-SRC{
            				leaf MAC-SRC-overwrite{
            					type yang:mac-address;
            				}
            			}
            			case IPv4-DST{
            				leaf IPv4-DST-overwrite{
            					type inet:ipv4-address;
            				}
            			}
            			case IPv4-SRC{
            				leaf IPv4-SRC-overwrite{
            					type inet:ipv4-address;
            				}
            			}
            			case L4-DST{
            				leaf L4-DST-overwrite{
            					type inet:port-number;
            				}
            			}
            			case L4-SRC{
            				leaf L4-SRC-overwrite{
            					type inet:port-number;
            				}
            			}
            		}
            }
            }
            case queue-action-case {
                container queue-action {
                    leaf queue {
                        type uint8;
                    }                    
                    }
            }
            }
            }
		grouping action-list {
				    list action {
				        key "order";
				        leaf order {
				            type int32;
				        }
				        uses action;
				    }
				}
    
    }
