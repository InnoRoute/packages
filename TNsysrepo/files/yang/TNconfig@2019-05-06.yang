module TNconfig {
    namespace "TrustNode:config";
    prefix TNconfig;
    
    description 
		"TrustNode basic configuration";
    revision "2019-05-06" {
        description "Initial revision";
    }
    grouping TrustNode {
        leaf Ethernet_Switch_enable {
					type boolean;
					description "enable hardware ethernet switch";
				}
				leaf Ethernet_Switch_aging {
					type uint8;
					description "hardware ethernet switch aging time";
				}
				        
        } 
        
        }
