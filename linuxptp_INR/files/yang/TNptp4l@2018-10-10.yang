module TNptp4l {

  	namespace "urn:sysrepo:TrustNode:TNptp4l";
  	prefix "tn";
	description  "Data model for TrustNode ptp4l";

  	revision 2018-10-10 {
    	description  "Initial revision.";
  	}




  /* State data and Configuration */

  	container TNptp4l {
    	description   "Data model for TrustNode ptp4l";
    	leaf pathdelay {
      		type int64;
      		config "false";
     		default 0;
      		description "ptp4l path delay";
    	}
    	leaf currenttime {
      		type int64;
      		config "false";
     		default 0;
      		description "ptp4l current time";
    	}
    	
    }
  
}
